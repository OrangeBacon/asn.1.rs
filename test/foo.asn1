MyModule { ident(5) } "/1/2" DEFINITIONS
HELLO INSTRUCTIONS
AUTOMATIC TAGS
EXTENSIBILITY IMPLIED ::= BEGIN
    EXPORTS a, b, c {};
    IMPORTS a, b FROM A A.b WITH SUCCESSORS
        c, d FROM B { 1 2 } WITH DESCENDANTS
        e FROM Z e WITH SUCCESSORS
        a, F FROM X
        G, z FROM A b c, d FROM X X.x;

    HELLO ::= BOOLEAN
    world BOOLEAN /*hello */::= TRUE
    stuff BOOLEAN ::= FALSE
    MyStuff ::= NULL
    foo NULL ::= NULL
    Iri ::= OID-IRI
    enc OID-IRI ::= "/ISO/Registration_Authority/19785.CBEFF/Organizations/JTC1-SC37/Patron-formats/TLV-encoded"
    MyInt ::= INTEGER { a(-5), b(Module.num) }
    a INTEGER ::= a -- comment
    b INTEGER --comment2--::= -3
    a ::= <INTEGER/>
    b ::= <Hello></Hello>
    c ::= <World><true/></World>
    d ::= <Foo>-5</Foo>
    e ::= <I>/a/b</I>
    F ::= ENUMERATED {
        a(5), b, c(7), ... !-5, z(3)
    }
    G ::= OBJECT IDENTIFIER
    h OBJECT IDENTIFIER ::= { iso standard 8571 application-context(1) }
    h OBJECT IDENTIFIER ::= { 1 0 8571 1 }
    i OBJECT IDENTIFIER ::= { A.b c(D.e) }
END

-- I believe this is an exhaustive list of all situations within the import
-- statement parser, hopefully
MyModule DEFINITIONS ::= BEGIN IMPORTS a, b FROM A; HELLO ::= BOOLEAN END
MyModule DEFINITIONS ::= BEGIN IMPORTS a, b FROM A { 1 2 }; HELLO ::= BOOLEAN END
MyModule DEFINITIONS ::= BEGIN IMPORTS a, b FROM A a; HELLO ::= BOOLEAN END
MyModule DEFINITIONS ::= BEGIN IMPORTS a, b FROM A A.a; HELLO ::= BOOLEAN END
MyModule DEFINITIONS ::= BEGIN IMPORTS a, b FROM A WITH SUCCESSORS; HELLO ::= BOOLEAN END
MyModule DEFINITIONS ::= BEGIN IMPORTS a, b FROM A a WITH SUCCESSORS; HELLO ::= BOOLEAN END
MyModule DEFINITIONS ::= BEGIN IMPORTS a, b FROM A A.a WITH SUCCESSORS; HELLO ::= BOOLEAN END

MyModule DEFINITIONS ::= BEGIN IMPORTS a, b FROM A c FROM D; HELLO ::= BOOLEAN END
MyModule DEFINITIONS ::= BEGIN IMPORTS a, b FROM A { 1 2 } c FROM D; HELLO ::= BOOLEAN END
MyModule DEFINITIONS ::= BEGIN IMPORTS a, b FROM A a c FROM D; HELLO ::= BOOLEAN END
MyModule DEFINITIONS ::= BEGIN IMPORTS a, b FROM A A.a c FROM D; HELLO ::= BOOLEAN END
MyModule DEFINITIONS ::= BEGIN IMPORTS a, b FROM A WITH SUCCESSORS c FROM D; HELLO ::= BOOLEAN END
MyModule DEFINITIONS ::= BEGIN IMPORTS a, b FROM A a WITH SUCCESSORS c FROM D; HELLO ::= BOOLEAN END
MyModule DEFINITIONS ::= BEGIN IMPORTS a, b FROM A A.a WITH SUCCESSORS c FROM D; HELLO ::= BOOLEAN END

MyModule DEFINITIONS ::= BEGIN IMPORTS a, b FROM A c, d FROM D; HELLO ::= BOOLEAN END
MyModule DEFINITIONS ::= BEGIN IMPORTS a, b FROM A { 1 2 } c, d FROM D; HELLO ::= BOOLEAN END
MyModule DEFINITIONS ::= BEGIN IMPORTS a, b FROM A a c, d FROM D; HELLO ::= BOOLEAN END
MyModule DEFINITIONS ::= BEGIN IMPORTS a, b FROM A A.a c, d FROM D; HELLO ::= BOOLEAN END
MyModule DEFINITIONS ::= BEGIN IMPORTS a, b FROM A WITH SUCCESSORS c, d FROM D; HELLO ::= BOOLEAN END
MyModule DEFINITIONS ::= BEGIN IMPORTS a, b FROM A a WITH SUCCESSORS c, d FROM D; HELLO ::= BOOLEAN END
MyModule DEFINITIONS ::= BEGIN IMPORTS a, b FROM A A.a WITH SUCCESSORS c, d FROM D; HELLO ::= BOOLEAN END

TestModule2 DEFINITIONS ::= BEGIN
    Test BOOLEAN ::= {}
    foo TestModule2.Test ::= TestModule2.foo
    bar ENUMERATED {
        a(5), b, c(7), ... !TestModule2.a, z(3)
    } ::= a
    ThisType ::= a < b < INTEGER
    val ThisType ::= a : '011001'B
    val2 Ty ::= CONTAINING INTEGER {a(5)} : BOOLEAN : a
    val3 INTEGER ::= -5.6e-7
    Val4 ::= Module.obj.&hello.&world
    Ty1 ::= BIT STRING
    Ty2 ::= BIT STRING {a(5), b(A.b)}
    Ty3 ::= [XER: UNIVERSAL 5] IMPLICIT OCTET STRING
    Ty4 ::= TYPE-IDENTIFIER.&test : ABSTRACT-SYNTAX : 4
    Ty5 ::= [stuff and things] INSTANCE OF ABSTRACT-SYNTAX
    Ty6 ::= [hello 678 "hi"] EXPLICIT EMBEDDED PDV

    ENCODING-CONTROL XER
        hello world "stuff here"!!{} [] aa
    ENCODING-CONTROL another
        one with more stuff
END -- hi --

TestModule3 DEFINITIONS ::= BEGIN
    A ::= SET OF a SEQUENCE {
        a INTEGER OPTIONAL,
        b BOOLEAN DEFAULT TRUE,
        COMPONENTS OF Test, ... !Except : 7,
        [[1: test Version1Type, test2 BIT STRING { a(5) } ]],
        c a < INTEGER,
        ...,
        d REAL,
    }
    B ::= SEQUENCE OF a A
    C ::= CHOICE {
        a BOOLEAN,
        b REAL,
        ...,
        c INTEGER {a(5)},
        [[d OCTET STRING, e EMBEDDED PDV]],
        ...
    }
    OPERATION ::= CLASS {
        &ArgumentType OPTIONAL,
        &ResultType OPTIONAL,
        &Errors ERROR OPTIONAL,
        &Linked OPERATION OPTIONAL,
        &resultReturned BOOLEAN DEFAULT TRUE,
        &operationCode INTEGER UNIQUE
    } WITH SYNTAX {
        [ARGUMENT &ArgumentType]
        [RESULT &ResultType]
        [RETURN RESULT &resultReturned]
        [ERRORS &Errors]
        [LINKED &Linked]
        CODE &operationCode
    }

    ERROR ::= CLASS {
        &ParameterType OPTIONAL,
        &errorCode INTEGER UNIQUE
    } WITH SYNTAX {
        [PARAMETER &ParameterType],
        [LITERAL [A &field] [B &field2]]
        CODE &errorCode
    }
END -- test --
